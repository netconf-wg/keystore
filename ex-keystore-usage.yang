module ex-keystore-usage {
  yang-version 1.1;
  namespace "https://example.com/ns/example-keystore-usage";
  prefix ex-keystore-usage;

  import ietf-keystore {
    prefix ks;
    reference
      "RFC CCCC: A YANG Data Model for a Keystore";
  }

  organization
    "Example Corporation";

  contact
    "Author: YANG Designer <mailto:yang.designer@example.com>";

  description
    "This example module illustrates notable groupings defined
     in the 'ietf-keystore' module.";

  revision YYYY-MM-DD {
    description
      "Initial version";
    reference
      "RFC CCCC: A YANG Data Model for a Keystore";
  }

  container keystore-usage {
    description
      "An illustration of the various keystore groupings.";
    list symmetric-key {
      key "name";
      leaf name {
        type string;
        description
          "An arbitrary name for this key.";
      }
      uses ks:inline-or-keystore-symmetric-key-grouping;
      description
        "An symmetric key that may be configured locally or be a
         reference to a symmetric key in the keystore.";
    }
    list asymmetric-key {
      key "name";
      leaf name {
        type string;
        description
          "An arbitrary name for this key.";
      }
      uses ks:inline-or-keystore-asymmetric-key-grouping;
      description
        "An asymmetric key, with no certs, that may be configured
         locally or be a reference to an asymmetric key in the
         keystore.  The intent is to reference just the asymmetric
         key, not any certificates that may also be associated
         with the asymmetric key.";
    }
    list asymmetric-key-with-certs {
      key "name";
      leaf name {
        type string;
        description
          "An arbitrary name for this key.";
      }
      uses ks:inline-or-keystore-asymmetric-key-with-certs-grouping;
      description
        "An asymmetric key and its associated certs, that may be
         configured locally or be a reference to an asymmetric key
         (and its associated certs) in the keystore.";
    }
    list end-entity-cert-with-key {
      key "name";
      leaf name {
        type string;
        description
          "An arbitrary name for this key.";
      }
      uses ks:inline-or-keystore-end-entity-cert-with-key-grouping;
      description
        "An end-entity certificate and its associated asymmetric
         key, that may be configured locally or be a reference
         to another certificate (and its associated asymmetric
         key) in the keystore.";
    }
  }
}
